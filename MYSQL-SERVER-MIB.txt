-- MySQL Server: SNMP Subagent
-- 
-- Copyright (C) 2008,2009 Brice Figureau
-- Copyright (C) 2008-2012 Days of Wonder, Inc.
--
-- This program is free software; you can redistribute it and/or
-- modify it under the terms of the GNU General Public License
-- as published by the Free Software Foundation; either version 2
-- of the License, or (at your option) any later version.
-- 
-- This program is distributed in the hope that it will be useful,
-- but WITHOUT ANY WARRANTY; without even the implied warranty of
-- MERCHANTABILITY or FITNESS FOR A PARTICULAR PURPOSE.  See the
-- GNU General Public License for more details.
-- 
-- You should have received a copy of the GNU General Public License
-- along with this program; if not, write to the Free Software
-- Foundation, Inc., 59 Temple Place - Suite 330, Boston, MA  02111-1307, USA.
--

MYSQL-SERVER-MIB DEFINITIONS ::= BEGIN

IMPORTS
    MODULE-IDENTITY, OBJECT-TYPE,
    enterprises, Counter32, Gauge32, Counter64
    FROM SNMPv2-SMI

    TEXTUAL-CONVENTION
    FROM SNMPv2-TC

    MODULE-COMPLIANCE, OBJECT-GROUP
    FROM SNMPv2-CONF;

mySQL		MODULE-IDENTITY
    LAST-UPDATED "201403110000Z"	-- Mar. 11, 2014
    ORGANIZATION "Days of Wonder, Inc."
    CONTACT-INFO
    "Days of Wonder
    334 State Street, Suite 203
    Los Altos, CA 94022
    USA"
    DESCRIPTION
    "This MIB describes a MySQL Database Server counters."

    REVISION "201403110000Z"	    -- Mar. 3, 2014
    DESCRIPTION
    "Added support for some wsrep/galera data"

    REVISION "201211220000Z"	    -- Nov. 22, 2012
    DESCRIPTION
    "Removed errors and warnings."

    REVISION "201108150000Z"	    -- Aug. 15, 2011
    DESCRIPTION
    "Added latest innodb values."

    REVISION "200807140000Z"	    -- Jul. 14, 2008
    DESCRIPTION
    "The original version of this MIB."

    ::= { enterprises daysofwonder(20267) 200 }

-- Current MySQL core MIB entries

MYSQLUnsigned64 ::= TEXTUAL-CONVENTION
		DISPLAY-HINT "d"
    STATUS  current
    DESCRIPTION
    "A 64 bits unsigned (which doesn't exist in SMIv2) containing any unsigned 64 bits
    integer number. It is defined as a Counter64 but doesn't carry the counter semantic"
    SYNTAX  Counter64

myStatus		OBJECT IDENTIFIER ::= { mySQL 1 }

myKeyReadRequests OBJECT-TYPE
    SYNTAX	Counter32
    MAX-ACCESS	read-only
    STATUS	current
    DESCRIPTION
    "The number of requests to read a key block
  	 from the cache."
    ::= { myStatus 1 }

myKeyReads OBJECT-TYPE
    SYNTAX	Counter32
    MAX-ACCESS	read-only
    STATUS	current
    DESCRIPTION
    "The number of physical reads of a key
  	 block from disk."
    ::= { myStatus 2 }

myKeyWriteRequests OBJECT-TYPE
    SYNTAX	Counter32
    MAX-ACCESS	read-only
    STATUS	current
    DESCRIPTION
    "The number of requests to write a key
  	 block to the cache."
    ::= { myStatus 3 }

myKeyWrites OBJECT-TYPE
    SYNTAX	Counter32
    MAX-ACCESS	read-only
    STATUS	current
    DESCRIPTION
    "The number of physical writes of a key
  	 block to disk."
    ::= { myStatus 4 }

myHistoryList OBJECT-TYPE
    SYNTAX	Gauge32
    MAX-ACCESS	read-only
    STATUS	current
    DESCRIPTION
    "InnoDB transaction history list length"
    ::= { myStatus 5 }

myInnodbTransactions OBJECT-TYPE
    SYNTAX	Counter64
    MAX-ACCESS	read-only
    STATUS	current
    DESCRIPTION
    "InnoDB transactions numbers"
    ::= { myStatus 6 }

myReadViews OBJECT-TYPE
    SYNTAX	Gauge32
    MAX-ACCESS	read-only
    STATUS	current
    DESCRIPTION
    "read views open inside InnoDB"
    ::= { myStatus 7 }

myCurrentTransactions OBJECT-TYPE
    SYNTAX	Gauge32
    MAX-ACCESS	read-only
    STATUS	current
    DESCRIPTION
    "Innodb number of transactions at one time"
    ::= { myStatus 8 }

myLockedTransactions OBJECT-TYPE
    SYNTAX	Gauge32
    MAX-ACCESS	read-only
    STATUS	current
    DESCRIPTION
    "Innodb number of locked transactions at one time"
    ::= { myStatus 9 }

myActiveTransactions OBJECT-TYPE
    SYNTAX	Gauge32
    MAX-ACCESS	read-only
    STATUS	current
    DESCRIPTION
    "Innodb number of active transactions at one time"
    ::= { myStatus 10 }

myPoolSize OBJECT-TYPE
    SYNTAX	Gauge32
    MAX-ACCESS	read-only
    STATUS	current
    DESCRIPTION
    "InnoDB Buffer Pool Size (pages)"
    ::= { myStatus 11 }

myFreePages OBJECT-TYPE
    SYNTAX	Gauge32
    MAX-ACCESS	read-only
    STATUS	current
    DESCRIPTION
    "InnoDB Free pages in Buffer Pool Size"
    ::= { myStatus 12 }

myDatabasePages OBJECT-TYPE
    SYNTAX	Gauge32
    MAX-ACCESS	read-only
    STATUS	current
    DESCRIPTION
    "InnoDB Page used for Database"
    ::= { myStatus 13 }

myModifiedPages OBJECT-TYPE
    SYNTAX	Gauge32
    MAX-ACCESS	read-only
    STATUS	current
    DESCRIPTION
    "InnoDB pages modified in Buffer Pool"
    ::= { myStatus 14 }

myPagesRead OBJECT-TYPE
    SYNTAX	Counter32
    MAX-ACCESS	read-only
    STATUS	current
    DESCRIPTION
    "InnoDB pages read"
    ::= { myStatus 15 }

myPagesCreated OBJECT-TYPE
    SYNTAX	Counter32
    MAX-ACCESS	read-only
    STATUS	current
    DESCRIPTION
    "InnoDB pages created"
    ::= { myStatus 16 }

myPagesWritten OBJECT-TYPE
    SYNTAX	Counter32
    MAX-ACCESS	read-only
    STATUS	current
    DESCRIPTION
    "InnoDB pages written"
    ::= { myStatus 17 }

myFileFsyncs OBJECT-TYPE
    SYNTAX	Counter32
    MAX-ACCESS	read-only
    STATUS	current
    DESCRIPTION
    "InnoDB fsyncs"
    ::= { myStatus 18 }

myFileReads OBJECT-TYPE
    SYNTAX	Counter32
    MAX-ACCESS	read-only
    STATUS	current
    DESCRIPTION
    "InnoDB fread"
    ::= { myStatus 19 }

myFileWrites OBJECT-TYPE
    SYNTAX	Counter32
    MAX-ACCESS	read-only
    STATUS	current
    DESCRIPTION
    "InnoDB fwrite"
    ::= { myStatus 20 }

myLogWrites OBJECT-TYPE
    SYNTAX	Counter32
    MAX-ACCESS	read-only
    STATUS	current
    DESCRIPTION
    "InnoDB log writes"
    ::= { myStatus 21 }

myPendingAIOLogIOs OBJECT-TYPE
    SYNTAX	Gauge32
    MAX-ACCESS	read-only
    STATUS	current
    DESCRIPTION
    "InnoDB Pending aio Log I/Os"
    ::= { myStatus 22 }

myPendingAIOSyncIOs OBJECT-TYPE
    SYNTAX	Gauge32
    MAX-ACCESS	read-only
    STATUS	current
    DESCRIPTION
    "InnoDB pending aio Sync I/Os"
    ::= { myStatus 23 }

myPendingBufPoolFlushes OBJECT-TYPE
    SYNTAX	Gauge32
    MAX-ACCESS	read-only
    STATUS	current
    DESCRIPTION
    "InnoDB pending Buffer Pool flushes"
    ::= { myStatus 24 }

myPendingChkpWrites OBJECT-TYPE
    SYNTAX	Gauge32
    MAX-ACCESS	read-only
    STATUS	current
    DESCRIPTION
    "InnoDB pending Checkpoint Writes"
    ::= { myStatus 25 }

myPendingIbufAIOReads OBJECT-TYPE
    SYNTAX	Gauge32
    MAX-ACCESS	read-only
    STATUS	current
    DESCRIPTION
    "InnoDB pending Insert Buffer AIO Reads"
    ::= { myStatus 26 }

myPendingLogFlushes OBJECT-TYPE
    SYNTAX	Gauge32
    MAX-ACCESS	read-only
    STATUS	current
    DESCRIPTION
    "InnoDB Pending Log Flushes"
    ::= { myStatus 27 }

myPendingLogWrites OBJECT-TYPE
    SYNTAX	Gauge32
    MAX-ACCESS	read-only
    STATUS	current
    DESCRIPTION
    "InnoDB Pending Log Writes"
    ::= { myStatus 28 }

myPendingNormalAIOReads OBJECT-TYPE
    SYNTAX	Gauge32
    MAX-ACCESS	read-only
    STATUS	current
    DESCRIPTION
    "InnoDB Pending Normal AIO reads"
    ::= { myStatus 29 }

myPendingNormalAIOWrites OBJECT-TYPE
    SYNTAX	Gauge32
    MAX-ACCESS	read-only
    STATUS	current
    DESCRIPTION
    "InnoDB Pending Normal AIO writes"
    ::= { myStatus 30 }

myIbufInserts OBJECT-TYPE
    SYNTAX	Counter32
    MAX-ACCESS	read-only
    STATUS	current
    DESCRIPTION
    "Innodb Insert Buffer inserts"
    ::= { myStatus 31 }

myIbufMerged OBJECT-TYPE
    SYNTAX	Counter32
    MAX-ACCESS	read-only
    STATUS	current
    DESCRIPTION
    "Innodb Insert Buffer merged"
    ::= { myStatus 32 }

myIbufMerges OBJECT-TYPE
    SYNTAX	Counter32
    MAX-ACCESS	read-only
    STATUS	current
    DESCRIPTION
    "InnoDB Insert Buffer merges"
    ::= { myStatus 33 }

mySpinWaits OBJECT-TYPE
    SYNTAX	Counter32
    MAX-ACCESS	read-only
    STATUS	current
    DESCRIPTION
    "InnoDB Spin Waits"
    ::= { myStatus 34 }

mySpinRounds OBJECT-TYPE
    SYNTAX	Counter32
    MAX-ACCESS	read-only
    STATUS	current
    DESCRIPTION
    "InnoDB Spin Rounds"
    ::= { myStatus 35 }

myOsWaits OBJECT-TYPE
    SYNTAX	Counter32
    MAX-ACCESS	read-only
    STATUS	current
    DESCRIPTION
    "InnoDB OS Waits"
    ::= { myStatus 36 }

myRowsInserted OBJECT-TYPE
    SYNTAX	Counter32
    MAX-ACCESS	read-only
    STATUS	current
    DESCRIPTION
    "InnoDB Rows Inserted"
    ::= { myStatus 37 }

myRowsUpdated OBJECT-TYPE
    SYNTAX	Counter32
    MAX-ACCESS	read-only
    STATUS	current
    DESCRIPTION
    "InnoDB Rows Updated"
    ::= { myStatus 38 }

myRowsDeleted OBJECT-TYPE
    SYNTAX	Counter32
    MAX-ACCESS	read-only
    STATUS	current
    DESCRIPTION
    "InnoDB Rows Deleted"
    ::= { myStatus 39 }

myRowsRead OBJECT-TYPE
    SYNTAX	Counter32
    MAX-ACCESS	read-only
    STATUS	current
    DESCRIPTION
    "InnoDB Rows Read"
    ::= { myStatus 40 }

myTableLocksWaited OBJECT-TYPE
    SYNTAX	Counter32
    MAX-ACCESS	read-only
    STATUS	current
    DESCRIPTION
    "Table Locks Waited"
    ::= { myStatus 41 }

myTableLocksImmediate OBJECT-TYPE
    SYNTAX	Counter32
    MAX-ACCESS	read-only
    STATUS	current
    DESCRIPTION
    "Table Locks Immediate"
    ::= { myStatus 42 }

mySlowQueries OBJECT-TYPE
    SYNTAX	Counter32
    MAX-ACCESS	read-only
    STATUS	current
    DESCRIPTION
    "Slow Queries"
    ::= { myStatus 43 }

myOpenFiles OBJECT-TYPE
    SYNTAX	Gauge32
    MAX-ACCESS	read-only
    STATUS	current
    DESCRIPTION
    "Open Files"
    ::= { myStatus 44 }

myOpenTables OBJECT-TYPE
    SYNTAX	Gauge32
    MAX-ACCESS	read-only
    STATUS	current
    DESCRIPTION
    "Open Tables"
    ::= { myStatus 45 }

myOpenedTables OBJECT-TYPE
    SYNTAX	Counter32
    MAX-ACCESS	read-only
    STATUS	current
    DESCRIPTION
    "Tables opened"
    ::= { myStatus 46 }

myInnodbOpenFiles OBJECT-TYPE
    SYNTAX	Counter32
    MAX-ACCESS	read-only
    STATUS	current
    DESCRIPTION
    "InnoDB open files"
    ::= { myStatus 47 }

myOpenFilesLimit OBJECT-TYPE
    SYNTAX	Counter32
    MAX-ACCESS	read-only
    STATUS	current
    DESCRIPTION
    "InnoDB open files limit"
    ::= { myStatus 48 }

myTableCache OBJECT-TYPE
    SYNTAX	Counter32
    MAX-ACCESS	read-only
    STATUS	current
    DESCRIPTION
    "Table Cache"
    ::= { myStatus 49 }

myAbortedClients OBJECT-TYPE
    SYNTAX	Counter32
    MAX-ACCESS	read-only
    STATUS	current
    DESCRIPTION
    "Aborted Clients"
    ::= { myStatus 50 }

myAbortedConnects OBJECT-TYPE
    SYNTAX	Counter32
    MAX-ACCESS	read-only
    STATUS	current
    DESCRIPTION
    "Aborted Connects"
    ::= { myStatus 51 }

myMaxUsedConnections OBJECT-TYPE
    SYNTAX	Counter32
    MAX-ACCESS	read-only
    STATUS	current
    DESCRIPTION
    "Max Used Connections"
    ::= { myStatus 52 }

mySlowLaunchThreads OBJECT-TYPE
    SYNTAX	Counter32
    MAX-ACCESS	read-only
    STATUS	current
    DESCRIPTION
  	"The number of threads that have taken
  	 more than slow_launch_time seconds to
  	 create."
    ::= { myStatus 53 }

myThreadsCached OBJECT-TYPE
    SYNTAX	Gauge32
    MAX-ACCESS	read-only
    STATUS	current
    DESCRIPTION
  	"The number of threads in the thread
  	 cache."
    ::= { myStatus 54 }

myThreadsConnected OBJECT-TYPE
    SYNTAX	Gauge32
    MAX-ACCESS	read-only
    STATUS	current
    DESCRIPTION
  	"The number of currently open
  	 connections."
    ::= { myStatus 55 }

myThreadsCreated OBJECT-TYPE
    SYNTAX	Counter32
    MAX-ACCESS	read-only
    STATUS	current
    DESCRIPTION
  	"The number of threads created to
  	 handle connections."
    ::= { myStatus 56 }

myThreadsRunning OBJECT-TYPE
    SYNTAX	Gauge32
    MAX-ACCESS	read-only
    STATUS	current
    DESCRIPTION
  	"The number of threads that are
  	 not sleeping."
    ::= { myStatus 57 }

myMaxConnections OBJECT-TYPE
    SYNTAX	Gauge32
    MAX-ACCESS	read-only
    STATUS	current
    DESCRIPTION
    "Number of maximal clients connected"
    ::= { myStatus 58 }

myThreadCacheSize OBJECT-TYPE
    SYNTAX	Gauge32
    MAX-ACCESS	read-only
    STATUS	current
    DESCRIPTION
  	"How many threads the server should cache for
  	 reuse."
    ::= { myStatus 59 }

myConnections OBJECT-TYPE
    SYNTAX	Counter32
    MAX-ACCESS	read-only
    STATUS	current
    DESCRIPTION
    "Number of clients connected"
    ::= { myStatus 60 }

mySlaveRunning OBJECT-TYPE
    SYNTAX	Gauge32
    MAX-ACCESS	read-only
    STATUS	current
    DESCRIPTION
    "Number of slaves connected"
    ::= { myStatus 61 }

mySlaveStopped OBJECT-TYPE
    SYNTAX	Gauge32
    MAX-ACCESS	read-only
    STATUS	current
    DESCRIPTION
    "Number of slaves stopped"
    ::= { myStatus 62 }

mySlaveRetriedTransactions OBJECT-TYPE
    SYNTAX	Counter32
    MAX-ACCESS	read-only
    STATUS	current
    DESCRIPTION
    "Number of transaction retried by slaves"
    ::= { myStatus 63 }

mySlaveLag OBJECT-TYPE
    SYNTAX	Gauge32
    MAX-ACCESS	read-only
    STATUS	current
    DESCRIPTION
    "Global slave time lag"
    ::= { myStatus 64 }

mySlaveOpenTempTables OBJECT-TYPE
    SYNTAX	Gauge32
    MAX-ACCESS	read-only
    STATUS	current
    DESCRIPTION
    "Number of temporary tables opened by slave"
    ::= { myStatus 65 }

myQcacheFreeBlocks OBJECT-TYPE
    SYNTAX	Gauge32
    MAX-ACCESS	read-only
    STATUS	current
    DESCRIPTION
    "Query Cache free blocks"
    ::= { myStatus 66 }

myQcacheFreeMemory OBJECT-TYPE
    SYNTAX	Gauge32
    MAX-ACCESS	read-only
    STATUS	current
    DESCRIPTION
    "Query cache free memory"
    ::= { myStatus 67 }

myQcacheHits OBJECT-TYPE
    SYNTAX	Counter32
    MAX-ACCESS	read-only
    STATUS	current
    DESCRIPTION
    "Number of Query cache hit"
    ::= { myStatus 68 }

myQcacheInserts OBJECT-TYPE
    SYNTAX	Counter32
    MAX-ACCESS	read-only
    STATUS	current
    DESCRIPTION
    "Number of Query Cache Inserts"
    ::= { myStatus 69 }

myQcacheLowmemPrunes OBJECT-TYPE
    SYNTAX	Counter32
    MAX-ACCESS	read-only
    STATUS	current
    DESCRIPTION
    "Number of Query Cache prunes for Low mem situation"
    ::= { myStatus 70 }

myQcacheNotCached OBJECT-TYPE
    SYNTAX	Counter32
    MAX-ACCESS	read-only
    STATUS	current
    DESCRIPTION
    "Number of query not cached"
    ::= { myStatus 71 }

myQcacheQueriesInCache OBJECT-TYPE
    SYNTAX	Gauge32
    MAX-ACCESS	read-only
    STATUS	current
    DESCRIPTION
    "Number of Queries cached in Query cache"
    ::= { myStatus 72 }

myQcacheTotalBlocks OBJECT-TYPE
    SYNTAX	Gauge32
    MAX-ACCESS	read-only
    STATUS	current
    DESCRIPTION
    "Number of blocks in Query Cache"
    ::= { myStatus 73 }

myQueryCacheSize OBJECT-TYPE
    SYNTAX	Counter32
    MAX-ACCESS	read-only
    STATUS	current
    DESCRIPTION
    "Query cache size"
    ::= { myStatus 74 }

myQuestions OBJECT-TYPE
    SYNTAX	Counter32
    MAX-ACCESS	read-only
    STATUS	current
    DESCRIPTION
    "Number of clients requests"
    ::= { myStatus 75 }

myComUpdate OBJECT-TYPE
    SYNTAX	Counter32
    MAX-ACCESS	read-only
    STATUS	current
    DESCRIPTION
    "Number of update query"
    ::= { myStatus 76 }

myComInsert OBJECT-TYPE
    SYNTAX	Counter32
    MAX-ACCESS	read-only
    STATUS	current
    DESCRIPTION
    "Number of insert queries"
    ::= { myStatus 77 }

myComSelect OBJECT-TYPE
    SYNTAX	Counter32
    MAX-ACCESS	read-only
    STATUS	current
    DESCRIPTION
    "Number of select queries"
    ::= { myStatus 78 }

myComDelete OBJECT-TYPE
    SYNTAX	Counter32
    MAX-ACCESS	read-only
    STATUS	current
    DESCRIPTION
    "Number of delete queries"
    ::= { myStatus 79 }

myComReplace OBJECT-TYPE
    SYNTAX	Counter32
    MAX-ACCESS	read-only
    STATUS	current
    DESCRIPTION
    "Number of replace queries"
    ::= { myStatus 80 }

myComLoad OBJECT-TYPE
    SYNTAX	Counter32
    MAX-ACCESS	read-only
    STATUS	current
    DESCRIPTION
    "Number of load queries"
    ::= { myStatus 81 }

myComUpdateMulti OBJECT-TYPE
    SYNTAX	Counter32
    MAX-ACCESS	read-only
    STATUS	current
    DESCRIPTION
    "Number of update-multi queries"
    ::= { myStatus 82 }

myComInsertSelect OBJECT-TYPE
    SYNTAX	Counter32
    MAX-ACCESS	read-only
    STATUS	current
    DESCRIPTION
    "Number of insert...select queries"
    ::= { myStatus 83 }

myComDeleteMulti OBJECT-TYPE
    SYNTAX	Counter32
    MAX-ACCESS	read-only
    STATUS	current
    DESCRIPTION
    "Number of delete-multi queries"
    ::= { myStatus 84 }

myComReplaceSelect OBJECT-TYPE
    SYNTAX	Counter32
    MAX-ACCESS	read-only
    STATUS	current
    DESCRIPTION
    "Number of replace..select queries"
    ::= { myStatus 85 }

mySelectFullJoin OBJECT-TYPE
    SYNTAX	Counter32
    MAX-ACCESS	read-only
    STATUS	current
    DESCRIPTION
    "Number of select full join queries"
    ::= { myStatus 86 }

mySelectFullRangeJoin OBJECT-TYPE
    SYNTAX	Counter32
    MAX-ACCESS	read-only
    STATUS	current
    DESCRIPTION
    "Number of select full range queries"
    ::= { myStatus 87 }

mySelectRange OBJECT-TYPE
    SYNTAX	Counter32
    MAX-ACCESS	read-only
    STATUS	current
    DESCRIPTION
    "Number of select range"
    ::= { myStatus 88 }

mySelectRangeCheck OBJECT-TYPE
    SYNTAX	Counter32
    MAX-ACCESS	read-only
    STATUS	current
    DESCRIPTION
    "Number of select ranche check"
    ::= { myStatus 89 }

mySelectScan OBJECT-TYPE
    SYNTAX	Counter32
    MAX-ACCESS	read-only
    STATUS	current
    DESCRIPTION
    "Number of select scan"
    ::= { myStatus 90 }

mySortMergePasses OBJECT-TYPE
    SYNTAX	Counter32
    MAX-ACCESS	read-only
    STATUS	current
    DESCRIPTION
    "Number of passes for filesorts"
    ::= { myStatus 91 }

mySortRange OBJECT-TYPE
    SYNTAX	Counter32
    MAX-ACCESS	read-only
    STATUS	current
    DESCRIPTION
    "Number of sorts done by range"
    ::= { myStatus 92 }

mySortRows OBJECT-TYPE
    SYNTAX	Counter32
    MAX-ACCESS	read-only
    STATUS	current
    DESCRIPTION
    "Number of sorted rows"
    ::= { myStatus 93 }

mySortScan OBJECT-TYPE
    SYNTAX	Counter32
    MAX-ACCESS	read-only
    STATUS	current
    DESCRIPTION
    "Number of sorts done by table scan"
    ::= { myStatus 94 }

myCreatedTmpTables OBJECT-TYPE
    SYNTAX	Counter32
    MAX-ACCESS	read-only
    STATUS	current
    DESCRIPTION
    "Number of tmp tables created"
    ::= { myStatus 95 }

myCreatedTmpDiskTables OBJECT-TYPE
    SYNTAX	Counter32
    MAX-ACCESS	read-only
    STATUS	current
    DESCRIPTION
    "Number of tmp disk tables created"
    ::= { myStatus 96 }

myCreatedTmpFiles OBJECT-TYPE
    SYNTAX	Counter32
    MAX-ACCESS	read-only
    STATUS	current
    DESCRIPTION
    "Number of tmp files created"
    ::= { myStatus 97 }

myBytesSent OBJECT-TYPE
    SYNTAX	Counter64
    MAX-ACCESS	read-only
    STATUS	current
    DESCRIPTION
    "Number of bytes sent"
    ::= { myStatus 98 }

myBytesReceived OBJECT-TYPE
    SYNTAX	Counter64
    MAX-ACCESS	read-only
    STATUS	current
    DESCRIPTION
    "Number of bytes received"
    ::= { myStatus 99 }

myInnodbLogBufferSize OBJECT-TYPE
    SYNTAX	Gauge32
    MAX-ACCESS	read-only
    STATUS	current
    DESCRIPTION
    "InnoDB log buffer size"
    ::= { myStatus 100 }

myUnflushedLog OBJECT-TYPE
    SYNTAX	Gauge32
    MAX-ACCESS	read-only
    STATUS	current
    DESCRIPTION
    "InnoDB unflushed log"
    ::= { myStatus 101 }

myLogBytesFlushed OBJECT-TYPE
    SYNTAX	Counter64
    MAX-ACCESS	read-only
    STATUS	current
    DESCRIPTION
    "InnoDB Logs bytes flushed to disk"
    ::= { myStatus 102 }

myLogBytesWritten OBJECT-TYPE
    SYNTAX	Counter64
    MAX-ACCESS	read-only
    STATUS	current
    DESCRIPTION
    "InnoDB logs bytes written"
    ::= { myStatus 103 }

myRelayLogSpace OBJECT-TYPE
    SYNTAX	Counter32
    MAX-ACCESS	read-only
    STATUS	current
    DESCRIPTION
    "Relay log free space"
    ::= { myStatus 104 }

myBinlogCacheSize OBJECT-TYPE
    SYNTAX	Gauge32
    MAX-ACCESS	read-only
    STATUS	current
    DESCRIPTION
    "Binlog cache size"
    ::= { myStatus 105 }

myBinlogCacheDiskUse OBJECT-TYPE
    SYNTAX	Counter32
    MAX-ACCESS	read-only
    STATUS	current
    DESCRIPTION
    "Binlog cache disk use"
    ::= { myStatus 106 }

myBinlogCacheUse OBJECT-TYPE
    SYNTAX	Counter32
    MAX-ACCESS	read-only
    STATUS	current
    DESCRIPTION
    "Binlog cache use"
    ::= { myStatus 107 }

myBinaryLogSpace OBJECT-TYPE
    SYNTAX	Counter32
    MAX-ACCESS	read-only
    STATUS	current
    DESCRIPTION
    "Total size of all binlogs"
    ::= { myStatus 108 }

myStateClosingTables OBJECT-TYPE
    SYNTAX	Gauge32
    MAX-ACCESS	read-only
    STATUS	current
    DESCRIPTION
    "Number of requests in closing state"
    ::= { myStatus 109 }

myStateCopyingToTmpTable OBJECT-TYPE
    SYNTAX	Gauge32
    MAX-ACCESS	read-only
    STATUS	current
    DESCRIPTION
    "Number of requests in copying to tmp table state"
    ::= { myStatus 110 }

myStateEnd OBJECT-TYPE
    SYNTAX	Gauge32
    MAX-ACCESS	read-only
    STATUS	current
    DESCRIPTION
    "Number of requests in end state"
    ::= { myStatus 111 }

myStateFreeingItems OBJECT-TYPE
    SYNTAX	Gauge32
    MAX-ACCESS	read-only
    STATUS	current
    DESCRIPTION
    "Number of requests in freeing items state"
    ::= { myStatus 112 }

myStateInit OBJECT-TYPE
    SYNTAX	Gauge32
    MAX-ACCESS	read-only
    STATUS	current
    DESCRIPTION
    "Number of requests in init state"
    ::= { myStatus 113 }

myStateLocked OBJECT-TYPE
    SYNTAX	Gauge32
    MAX-ACCESS	read-only
    STATUS	current
    DESCRIPTION
    "Number of requests in locked state"
    ::= { myStatus 114 }

myStateLogin OBJECT-TYPE
    SYNTAX	Gauge32
    MAX-ACCESS	read-only
    STATUS	current
    DESCRIPTION
    "Number of requests in login state"
    ::= { myStatus 115 }

myStatePreparing OBJECT-TYPE
    SYNTAX	Gauge32
    MAX-ACCESS	read-only
    STATUS	current
    DESCRIPTION
    "Number of requests in preparing state"
    ::= { myStatus 116 }

myStateReadingFromNet OBJECT-TYPE
    SYNTAX	Gauge32
    MAX-ACCESS	read-only
    STATUS	current
    DESCRIPTION
    "Number of requests in reading from net state"
    ::= { myStatus 117 }

myStateSendingData OBJECT-TYPE
    SYNTAX	Gauge32
    MAX-ACCESS	read-only
    STATUS	current
    DESCRIPTION
    "Number of requests in sending data state"
    ::= { myStatus 118 }

myStateSortingResult OBJECT-TYPE
    SYNTAX	Gauge32
    MAX-ACCESS	read-only
    STATUS	current
    DESCRIPTION
    "Number of requests in sorting result state"
    ::= { myStatus 119 }

myStateStatistics OBJECT-TYPE
    SYNTAX	Gauge32
    MAX-ACCESS	read-only
    STATUS	current
    DESCRIPTION
    "Number of requests in statistics state"
    ::= { myStatus 120 }

myStateUpdating OBJECT-TYPE
    SYNTAX	Gauge32
    MAX-ACCESS	read-only
    STATUS	current
    DESCRIPTION
    "Number of requests in updating state"
    ::= { myStatus 121 }

myStateWritingToNet OBJECT-TYPE
    SYNTAX	Gauge32
    MAX-ACCESS	read-only
    STATUS	current
    DESCRIPTION
    "Number of requests in writing to net state"
    ::= { myStatus 122 }

myStateNone OBJECT-TYPE
    SYNTAX	Gauge32
    MAX-ACCESS	read-only
    STATUS	current
    DESCRIPTION
    "Number of requests in none state"
    ::= { myStatus 123 }

myStateOther OBJECT-TYPE
    SYNTAX	Gauge32
    MAX-ACCESS	read-only
    STATUS	current
    DESCRIPTION
    "Number of requests in other state"
    ::= { myStatus 124 }

myAdditionalPoolAlloc OBJECT-TYPE
    SYNTAX	MYSQLUnsigned64
    MAX-ACCESS	read-only
    STATUS	current
    DESCRIPTION
    "Number of bytes allocated in the additional pool"
    ::= { myStatus 125 }

myTotalMemAlloc OBJECT-TYPE
    SYNTAX	MYSQLUnsigned64
    MAX-ACCESS	read-only
    STATUS	current
    DESCRIPTION
    "Number of bytes allocated by MySQL"
    ::= { myStatus 126 }

myHashIndexCellsTotal OBJECT-TYPE
    SYNTAX	Gauge32
    MAX-ACCESS	read-only
    STATUS	current
    DESCRIPTION
    "TBD"
    ::= { myStatus 127 }

myHashIndexCellsUsed OBJECT-TYPE
    SYNTAX	Gauge32
    MAX-ACCESS	read-only
    STATUS	current
    DESCRIPTION
    "TBD"
    ::= { myStatus 128 }

myInnoDBLockStructs OBJECT-TYPE
    SYNTAX	Gauge32
    MAX-ACCESS	read-only
    STATUS	current
    DESCRIPTION
    "TBD"
    ::= { myStatus 129 }

myInnoDBLockWaitSecs OBJECT-TYPE
    SYNTAX	Gauge32
    MAX-ACCESS	read-only
    STATUS	current
    DESCRIPTION
    "TBD"
    ::= { myStatus 130 }

myInnoDBTablesInUse OBJECT-TYPE
    SYNTAX	Gauge32
    MAX-ACCESS	read-only
    STATUS	current
    DESCRIPTION
    "Number of innodb tables in use"
    ::= { myStatus 131 }

myInnoDBLockedTables OBJECT-TYPE
    SYNTAX	Gauge32
    MAX-ACCESS	read-only
    STATUS	current
    DESCRIPTION
    "Number of locked tables by the innodb subsystem"
    ::= { myStatus 132 }

myUncheckpointedBytes OBJECT-TYPE
    SYNTAX	Gauge32
    MAX-ACCESS	read-only
    STATUS	current
    DESCRIPTION
    "Number of not yet checkpointed bytes"
    ::= { myStatus 133 }

myIBufCellCount OBJECT-TYPE
    SYNTAX	Gauge32
    MAX-ACCESS	read-only
    STATUS	current
    DESCRIPTION
    "Number of insert buffer cells"
    ::= { myStatus 134 }

myIBufUsedCells OBJECT-TYPE
    SYNTAX	Gauge32
    MAX-ACCESS	read-only
    STATUS	current
    DESCRIPTION
    "Number of insert buffer used cells"
    ::= { myStatus 135 }

myIBufFreeCells OBJECT-TYPE
    SYNTAX	Gauge32
    MAX-ACCESS	read-only
    STATUS	current
    DESCRIPTION
    "Number of insert buffer free cells"
    ::= { myStatus 136 }

myAdaptiveHashMemory OBJECT-TYPE
    SYNTAX	MYSQLUnsigned64
    MAX-ACCESS	read-only
    STATUS	current
    DESCRIPTION
    "InnoDB hash memory used"
    ::= { myStatus 137 }

myPageHashMemory OBJECT-TYPE
    SYNTAX	MYSQLUnsigned64
    MAX-ACCESS	read-only
    STATUS	current
    DESCRIPTION
    "InnoDB page hash memory used"
    ::= { myStatus 138 }

myDictionaryCacheMemory OBJECT-TYPE
    SYNTAX	MYSQLUnsigned64
    MAX-ACCESS	read-only
    STATUS	current
    DESCRIPTION
    "InnoDB dictionary cache memory used"
    ::= { myStatus 139 }

myFileSystemMemory OBJECT-TYPE
    SYNTAX	MYSQLUnsigned64
    MAX-ACCESS	read-only
    STATUS	current
    DESCRIPTION
    "InnoDB file system memory used"
    ::= { myStatus 140 }

myLockSystemMemory OBJECT-TYPE
    SYNTAX	MYSQLUnsigned64
    MAX-ACCESS	read-only
    STATUS	current
    DESCRIPTION
    "InnoDB lock system memory used"
    ::= { myStatus 141 }

myRecoverySystemMemory OBJECT-TYPE
    SYNTAX	MYSQLUnsigned64
    MAX-ACCESS	read-only
    STATUS	current
    DESCRIPTION
    "InnoDB recovery system memory used"
    ::= { myStatus 142 }

myThreadHashMemory OBJECT-TYPE
    SYNTAX	MYSQLUnsigned64
    MAX-ACCESS	read-only
    STATUS	current
    DESCRIPTION
    "InnoDB thread hash memory used"
    ::= { myStatus 143 }

myInnoDBSemWaits OBJECT-TYPE
    SYNTAX	Counter64
    MAX-ACCESS	read-only
    STATUS	current
    DESCRIPTION
    "Number of time innodb waited for semaphores"
    ::= { myStatus 144 }

myInooDBSemWaitTime OBJECT-TYPE
    SYNTAX	Counter64
    MAX-ACCESS	read-only
    STATUS	current
    DESCRIPTION
    "Total time innodb waited for semaphores"
    ::= { myStatus 145 }

myKeyBufBytesUnflushed OBJECT-TYPE
    SYNTAX	MYSQLUnsigned64
    MAX-ACCESS	read-only
    STATUS	current
    DESCRIPTION
    "Key Buffer bytes still unflushed"
    ::= { myStatus 146 }

myKeyBufBytesUsed OBJECT-TYPE
    SYNTAX	MYSQLUnsigned64
    MAX-ACCESS	read-only
    STATUS	current
    DESCRIPTION
    "Key Buffer used in bytes"
    ::= { myStatus 147 }

myKeyBufferSize OBJECT-TYPE
    SYNTAX	MYSQLUnsigned64
    MAX-ACCESS	read-only
    STATUS	current
    DESCRIPTION
    "Size of the Key Buffer"
    ::= { myStatus 148 }

myInnoDBRowLockTime OBJECT-TYPE
    SYNTAX	MYSQLUnsigned64
    MAX-ACCESS	read-only
    STATUS	current
    DESCRIPTION
    "Total time (ms) spent in acquiring row locks"
    ::= { myStatus 149 }

myInnoDBRowLockWaits OBJECT-TYPE
    SYNTAX	MYSQLUnsigned64
    MAX-ACCESS	read-only
    STATUS	current
    DESCRIPTION
    "The number of times a row lock had to be waited for"
    ::= { myStatus 150 }

myWsrepClusterStateUuid OBJECT-TYPE
    SYNTAX	OCTET STRING
    MAX-ACCESS	read-only
    STATUS	current
    DESCRIPTION
    "UUID for the cluster"
    ::= { myStatus 151 }

myWsrepClusterConfId OBJECT-TYPE
    SYNTAX	INTEGER
    MAX-ACCESS	read-only
    STATUS	current
    DESCRIPTION
    "wsrep conf id for the cluster"
    ::= { myStatus 152 }

myWsrepClusterSize OBJECT-TYPE
    SYNTAX	INTEGER
    MAX-ACCESS	read-only
    STATUS	current
    DESCRIPTION
    "Number of online nodes in the cluster"
    ::= { myStatus 153 }

myWsrepClusterStatus OBJECT-TYPE
    SYNTAX	OCTET STRING
    MAX-ACCESS	read-only
    STATUS	current
    DESCRIPTION
    "Cluster status"
    ::= { myStatus 154 }

myWsrepReady OBJECT-TYPE
    SYNTAX	OCTET STRING
    MAX-ACCESS	read-only
    STATUS	current
    DESCRIPTION
    "Node can accept SQL load"
    ::= { myStatus 155 }

myWsrepConnected OBJECT-TYPE
    SYNTAX	OCTET STRING
    MAX-ACCESS	read-only
    STATUS	current
    DESCRIPTION
    "Cluster connection status"
    ::= { myStatus 156 }

myWsrepLocalStateComment OBJECT-TYPE
    SYNTAX	OCTET STRING
    MAX-ACCESS	read-only
    STATUS	current
    DESCRIPTION
    "Description of local state"
    ::= { myStatus 157 }

myWsrepFlowControlPaused OBJECT-TYPE
    SYNTAX	OCTET STRING
    MAX-ACCESS	read-only
    STATUS	current
    DESCRIPTION
    "indicates the fraction of time replication was paused since last SHOW
    STATUS"
    ::= { myStatus 158 }

myWsrepReplicatedBytes OBJECT-TYPE
    SYNTAX	Counter64
    MAX-ACCESS	read-only
    STATUS	current
    DESCRIPTION
    "Number of bytes replicated"
    ::= { myStatus 159 }

myWsrepReceivedBytes OBJECT-TYPE
    SYNTAX	Counter64
    MAX-ACCESS	read-only
    STATUS	current
    DESCRIPTION
    "Number of wsrep bytes received"
    ::= { myStatus 160 }


-- conformance information

mySQLMIBConformance OBJECT IDENTIFIER ::= { mySQL 2 }

mySQLMIBCompliances OBJECT IDENTIFIER ::= { mySQLMIBConformance 1 }
mySQLMIBGroups      OBJECT IDENTIFIER ::= { mySQLMIBConformance 2 }

-- compliance statements

mySQLMIBCompliance MODULE-COMPLIANCE
    STATUS  current
    DESCRIPTION
    "The compliance statement for SNMPv2 entities which implement MYSQL."
    MODULE  -- this module
    MANDATORY-GROUPS { mySQLGroup }
    ::= { mySQLMIBCompliances 1 }

-- units of conformance

mySQLGroup OBJECT-GROUP
    OBJECTS   { 
			myKeyReadRequests,
			myKeyReads,
			myKeyWriteRequests,
			myKeyWrites,
			myHistoryList,
			myInnodbTransactions,
			myReadViews,
			myCurrentTransactions,
			myLockedTransactions,
			myActiveTransactions,
			myPoolSize,
			myFreePages,
			myDatabasePages,
			myModifiedPages,
			myPagesRead,
			myPagesCreated,
			myPagesWritten,
			myFileFsyncs,
			myFileReads,
			myFileWrites,
			myLogWrites,
			myPendingAIOLogIOs,
			myPendingAIOSyncIOs,
			myPendingBufPoolFlushes,
			myPendingChkpWrites,
			myPendingIbufAIOReads,
			myPendingLogFlushes,
			myPendingLogWrites,
			myPendingNormalAIOReads,
			myPendingNormalAIOWrites,
			myIbufInserts,
			myIbufMerged,
			myIbufMerges,
			mySpinWaits,
			mySpinRounds,
			myOsWaits,
			myRowsInserted,
			myRowsUpdated,
			myRowsDeleted,
			myRowsRead,
			myTableLocksWaited,
			myTableLocksImmediate,
			mySlowQueries,
			myOpenFiles,
			myOpenTables,
			myOpenedTables,
			myInnodbOpenFiles,
			myOpenFilesLimit,
			myTableCache,
			myAbortedClients,
			myAbortedConnects,
			myMaxUsedConnections,
			mySlowLaunchThreads,
			myThreadsCached,
			myThreadsConnected,
			myThreadsCreated,
			myThreadsRunning,
			myMaxConnections,
			myThreadCacheSize,
			myConnections,
			mySlaveRunning,
			mySlaveStopped,
			mySlaveRetriedTransactions,
			mySlaveLag,
			mySlaveOpenTempTables,
			myQcacheFreeBlocks,
			myQcacheFreeMemory,
			myQcacheHits,
			myQcacheInserts,
			myQcacheLowmemPrunes,
			myQcacheNotCached,
			myQcacheQueriesInCache,
			myQcacheTotalBlocks,
			myQueryCacheSize,
			myQuestions,
			myComUpdate,
			myComInsert,
			myComSelect,
			myComDelete,
			myComReplace,
			myComLoad,
			myComUpdateMulti,
			myComInsertSelect,
			myComDeleteMulti,
			myComReplaceSelect,
			mySelectFullJoin,
			mySelectFullRangeJoin,
			mySelectRange,
			mySelectRangeCheck,
			mySelectScan,
			mySortMergePasses,
			mySortRange,
			mySortRows,
			mySortScan,
			myCreatedTmpTables,
			myCreatedTmpDiskTables,
			myCreatedTmpFiles,
			myBytesSent,
			myBytesReceived,
			myInnodbLogBufferSize,
			myUnflushedLog,
			myLogBytesFlushed,
			myLogBytesWritten,
			myRelayLogSpace,
			myBinlogCacheSize,
			myBinlogCacheDiskUse,
			myBinlogCacheUse,
			myBinaryLogSpace,
			myStateClosingTables,
			myStateCopyingToTmpTable,
			myStateEnd,
			myStateFreeingItems,
			myStateInit,
			myStateLocked,
			myStateLogin,
			myStatePreparing,
			myStateReadingFromNet,
			myStateSendingData,
			myStateSortingResult,
			myStateStatistics,
			myStateUpdating,
			myStateWritingToNet,
			myStateNone,
			myStateOther,
			myAdditionalPoolAlloc,
			myTotalMemAlloc,
			myHashIndexCellsTotal,
			myHashIndexCellsUsed,
			myInnoDBLockStructs,
			myInnoDBLockWaitSecs,
			myInnoDBTablesInUse,
			myInnoDBLockedTables,
			myUncheckpointedBytes,
			myIBufCellCount,
			myIBufUsedCells,
			myIBufFreeCells,
			myAdaptiveHashMemory,
			myPageHashMemory,
			myDictionaryCacheMemory,
			myFileSystemMemory,
			myLockSystemMemory,
			myRecoverySystemMemory,
			myThreadHashMemory,
			myInnoDBSemWaits,
			myInooDBSemWaitTime,
			myKeyBufBytesUnflushed,
			myKeyBufBytesUsed,
			myKeyBufferSize,
			myInnoDBRowLockTime,
			myInnoDBRowLockWaits,
            myWsrepClusterStateUuid,
            myWsrepClusterConfId,
            myWsrepClusterSize,
            myWsrepClusterStatus,
            myWsrepReady,
            myWsrepConnected,
            myWsrepLocalStateComment,
            myWsrepFlowControlPaused,
            myWsrepReplicatedBytes,
            myWsrepReceivedBytes

}
    STATUS    current
    DESCRIPTION
     "The group of objects providing for management of MYSQL entities."
    ::= { mySQLMIBGroups 1 }


END
